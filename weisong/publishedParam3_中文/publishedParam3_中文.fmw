FME workspace publishedParam3_中文.fmw

Parameters:
- AttributeListCSV =
- AttributeListSpace =
- AttributeName =
- Choice =
- ChoiceAlias =
- ChoiceAliasMultiple =
- ChoiceMultiple =
- ChoiceOrText =
- ColorPicker =
- CoordinateSystemName =
- Date =
- Date_Time =
- DestDataset_CSV2 =
- FilenameExisting =
- FilenameMultiple =
- FilenameOutput =
- FolderExisting =
- FolderOutput =
- Number =
- Password =
- Text =
- TextMultiline =
- TextMultilineNumber =
- URL =

Writers:
- CSV2_1: CSV2 to $(DestDataset_CSV2)

Creator
    GEOMTYPE = Geometry Object
    NUM = 1
    CREATED -> AttributeCreator
AttributeCreator
    ATTR_TABLE:
      SET_TO Attribute1 = attr1Value
      SET_TO Attribute2 = attr2Value
      SET_TO Attribute3 = attr3Value
    -> ParameterFetcher
ParameterFetcher
    ATTR_LIST = AttributeListCSV $(AttributeListCSV) AttributeListSpace $(AttributeListSpace) AttributeName $(AttributeName) Choice $(Choice) ChoiceAlias $(ChoiceAlias) ChoiceAliasMultiple $(ChoiceAliasMultiple) ChoiceMultiple $(ChoiceMultiple) ChoiceOrText $(ChoiceOrText) ColorPicker $(ColorPicker) CoordinateSystemName $(CoordinateSystemName) DateTime $(Date_Time) FilenameExisting $(FilenameExisting) FilenameMultiple $(FilenameMultiple) FilenameOutput $(FilenameOutput) FolderExisting $(FolderExisting) FolderOutput $(FolderOutput) Number $(Number) Password $(Password) Text $(Text) TextMultiline $(TextMultiline) TextMultilineNumber $(TextMultilineNumber) URL $(URL) Date $(Date)
    -> pubParamResultFile (writer CSV2_1)
pubParamResultFile (writer CSV2_1)
    attributes: AttributeListCSV string, AttributeListSpace string, AttributeName string, Choice string, ChoiceAlias string, ChoiceAliasMultiple string, ChoiceMultiple string, ChoiceOrText string, ColorPicker string, CoordinateSystemName string, DateTime string, FilenameExisting string, FilenameMultiple string, FilenameOutput string, FolderExisting string, FolderOutput string, Number string, Password string, Text string, TextMultiline string, TextMultilineNumber string, URL string, Date string
